module vyatta-resources-chap-v1 {
	namespace "urn:vyatta.com:mgmt:vyatta-resources-chap:1";
	prefix vyatta-resources-chap-v1;

	import configd-v1 {
		prefix configd;
	}

	import vyatta-resources-v1 {
		prefix resources;
	}

	import ietf-inet-types {
		prefix inet;
	}

	organization "AT&T Inc.";
	contact
		"AT&T
		Postal: 208 S. Akard Street
			Dallas, TX 75202
			USA
		Web: www.att.com";

	description
		"Copyright (c) 2017-2019, AT&T Intellectual Property.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 CHAP secrets modeled in Yang. Does a non-destructive update to the
		 /etc/ppp/chap-secrets file.";

	revision 2019-07-04 {
		description "Support CHAP user-name/secrets with up to 255 characeters";
	}

	revision 2017-08-10 {
		description "Initial revision";
	}

	augment /resources:resources {
		container chap-secrets {
			presence 'Enables CHAP secrets';
			configd:help "Chap authentication information";
			configd:end "/opt/vyatta/sbin/vyatta-update-chap";
			list user {
				description "List of chap users configured on the system.";
				configd:help "User login information";
				key "name";
				leaf name {
					type string {
						length 1..255;
						pattern '[\S]*';
					}
					description "Short string specifying the username.";
					configd:help "CHAP user name";
				}
				leaf server {
					type union {
						type inet:domain-name;
						type inet:ip-address;
					}
					description "IP or hostname of the PPPoE remote tunnel end.";
					configd:help "Address or hostname of the remote host";
				}
				leaf secret {
					type string {
						length 1..255;
						pattern '[\S]*';
					}
					mandatory true;
					description "Secret login string.";
					configd:secret true;
					configd:help "Secret login string";
				}
				leaf-list local-addresses {
					type inet:ip-address;
					description "List of IP address assignable to the local PPPoE tunnel end.";
					configd:help "List of acceptable local addresses.";
				}
			}
		}
	}
}
