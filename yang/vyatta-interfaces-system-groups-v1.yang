module vyatta-interfaces-system-groups-v1 {
	namespace "urn:vyatta.com:mgmt:vyatta-interfaces-system-groups-v1:1";
	prefix interfaces-system-groups;

	import vyatta-types-v1 {
		prefix types;
	}
	import configd-v1 {
		prefix configd;
	}
	import vyatta-interfaces-v1 {
		prefix if;
	}
	import vyatta-ipv6-rtradv-groups-v1 {
		prefix ipv6-rtradv;
	}

	organization "AT&T Inc.";
	contact
		"AT&T
		 Postal: 208 S. Akard Street
		         Dallas, TX 75202
		         USA
		 Web: www.att.com";

	description
		"Copyright (c) 2017-2019, AT&T Intellectual Property.
		 All rights reserved.

		 Copyright (c) 2016 by Brocade Communication Systems, Inc.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Common attribute groupings for local (administrative) system
		 interfaces
		";

	revision 2016-08-25 {
		description "Initial revision for version 1";
	}

	grouping if-parameters-sys {
		description "Base set of attributes for use by system (host) interfaces";

		leaf-list address {
			type if:address-dhcp;
			ordered-by "user";
			description "IP address";
			configd:help "IP address";
			configd:create "vyatta-address add $VAR(../@) $VAR(@)";
			configd:delete "vyatta-address delete $VAR(../@) $VAR(@)";
			configd:allowed "echo 'dhcp dhcpv6 <>'";
		}

		leaf mtu {
			type uint32 {
				range 68..9000;
			}
			description "Maximum Transmission Unit (MTU)";
			default "1500";

			configd:help "Maximum Transmission Unit (MTU)";
			configd:update "perl -e 'system \"ip link set $VAR(../@) mtu $VAR(@)\" if -d \"/sys/class/net/$VAR(../@)\";'";
		}

		leaf mac {
			type types:mac-address;
			description "Media Access Control (MAC) address";
			configd:help "Media Access Control (MAC) address";
			configd:validate "vyatta-interfaces.pl --dev $VAR(../@) --valid-mac $VAR(@)";
			configd:update "vyatta-interfaces.pl --dev $VAR(../@) --set-mac $VAR(@)";
			configd:delete "vyatta-interfaces.pl --dev $VAR(../@) --del-mac";
		}

		uses if:if-parameters-host {
			augment ipv6 {
				uses ipv6-rtradv:if-ipv6-parameters-host;
			}
		}
	}

	grouping vif-parameters-sys {
		description "Base set of attributes for use by system (host) sub-interfaces";

		leaf-list address {
			type if:address-dhcp;
			ordered-by "user";
			description "IP address";
			configd:help "IP address";
			configd:create "vyatta-address add $VAR(../../@).$VAR(../@) $VAR(@)";
			configd:delete "vyatta-address delete $VAR(../../@).$VAR(../@) $VAR(@)";
			configd:allowed "echo 'dhcp dhcpv6 <>'";
		}

		leaf mtu {
			type uint32 {
				range 68..9000;
			}
			description "Maximum Transmission Unit (MTU) for VIF sub-interfaces";
			must "((current()) < ../../mtu)" {
				error-message "MTU of VIF interface must be less than MTU of parent interface";
			}

			configd:help "Maximum Transmission Unit (MTU) for VIF Sub-interfaces";
			configd:update "vyatta-interfaces.pl --dev $VAR(../../@) --update-vif $VAR(../@) --set-mtu $VAR(@)";
			configd:delete "vyatta-interfaces.pl --dev $VAR(../../@) --update-vif $VAR(../@) --del-mtu 1500";
		}

		leaf vlan {
			type uint32 {
				range 1..4094;
			}
			description "Virtual Local Area Network (VLAN) ID";
			configd:help "Virtual Local Area Network (VLAN) ID";
			configd:update "vyatta-interfaces.pl --dev $VAR(../../@) --update-vif $VAR(../@) --update-vlan";
			configd:delete "vyatta-interfaces.pl --dev $VAR(../../@) --update-vif $VAR(../@) --delete-vlan";
		}

		leaf inner-vlan {
			type uint32 {
				range 1..4094;
			}
			description "Virtual Local Area Network (VLAN) ID";
			configd:help "Virtual Local Area Network (VLAN) ID";
			configd:update "vyatta-interfaces.pl --dev $VAR(../../@) --update-vif $VAR(../@) --update-ivlan";
			configd:delete "vyatta-interfaces.pl --dev $VAR(../../@) --update-vif $VAR(../@) --del-ivlan";
		}

		uses if:vif-description;
		uses if:vif-parameters-host {
			augment ipv6 {
				uses ipv6-rtradv:vif-ipv6-parameters-host;
			}
		}
	}
}
