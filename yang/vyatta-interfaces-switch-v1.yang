module vyatta-interfaces-switch-v1 {
	namespace "urn:vyatta.com:mgmt:vyatta-interfaces-switch:1";
	prefix vyatta-interfaces-switch-v1;

	import vyatta-interfaces-v1 {
		prefix if;
	}
	import configd-v1 {
		prefix configd;
	}
	import vyatta-types-v1 {
		prefix types;
	}
	import vyatta-interfaces-vif-v2 {
		prefix vif;
	}
	import vyatta-system-v1 {
		prefix sys;
	}
	import vyatta-system-platform-v1 {
		prefix platf;
	}
	import vyatta-interfaces-bridge-state-v1 {
		prefix br-state;
	}
	import vyatta-services-v1 {
		prefix service;
	}
	import vyatta-service-portmonitor-v1 {
		prefix pm;
	}

	organization "AT&T Inc.";
	contact
		"AT&T
		 Postal: 208 S. Akard Street
		         Dallas, TX 75202
		         USA
		 Web: www.att.com";

	description
		"Copyright (c) 2017-2020, AT&T Intellectual Property.
		 All rights reserved.

		 Copyright (c) 2016-2017 by Brocade Communications Systems, Inc.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 The YANG module for vyatta-interfaces-switch-v1.
		 This module provides support for VLAN aware bridges called
		 switches.  Each port that is part of a switch may have a set of
		 allowed VLANs, a PVID, and a set of VLANs to untag on egress
		 from a port.";

	revision 2020-08-30 {
		description "Add configd:must for more efficient VIF validation";
	}
	revision 2020-07-30 {
		description "Add end action to handle portmonitor updates";
	}
	revision 2019-10-11 {
		description "QoS config moved to VCI, call to qos-commit.pl removed";
	}
	revision 2019-07-04 {
		description "Add multicast-router leaf to enable multicast forwarding on the switch";
	}
	revision 2019-04-15 {
		description
			"Mark the switch operational forwarding-database element as
			deprecated. The forwarding-database does not scale and has
			been replaced with an object that provides a summary of
			the forwarding database.

			Access to the full forwarding database is through a
			NETCONF RPC function.";
	}
	revision 2019-02-05 {
		description "Move switch interface processing at the interfaces level
			     and restore switch vlan processing in the switch level";
	}
	revision 2019-01-18 {
		description "Use bridge functions to update or delete switch MAC address";
	}
	revision 2018-10-19 {
		description "Added bpdu-filter details to switch-state";
	}
	revision 2018-10-01 {
		description "Add end action to handle vif updates";
	}
	revision 2018-09-24 {
		description "Split out vyatta-switch logic to improve performance.";
	}
	revision 2018-08-27 {
		description "Added the qos-parameters CLI under vlan-parameters
			    for the interface switch-group CLI.
			    Convert switch MAC validation to YANG";
	}
	revision 2018-07-25 {
		description "Add support for per VLAN statistics";
	}
	revision 2018-03-20 {
		description "Add physical-switch node. Add actions to set interface
                     default state when platform type or interface config change";
	}
	revision 2018-02-27 {
		description "Initial revision";
	}

	typedef port-mode {
		type enumeration {
			enum trunk {
				configd:help "Allow multiple VLANs on this port";
				description "Allow multiple VLANs on this port";
			}
			enum access {
				configd:help "Only allow untagged VLANs on this port";
				description "Only allow untagged VLANs on this port";
			}
		}
	}

	typedef vlan-id {
		type uint16 {
			range 1..4094;
		}
	}

	typedef fdb-state {
		status obsolete;
		type br-state:fdb-state;
	}

	typedef bridge-port-state {
		status obsolete;
		type br-state:bridge-port-state;
	}

	typedef bridge-port-role {
		status obsolete;
		type br-state:bridge-port-role;
	}

	grouping port-parameters {
		leaf mode {
			type port-mode;
			must "not(current() = 'access') or " +
			     "../vlan-parameters/primary-vlan-id" {
				error-message "Primary VLAN ID must be supplied in access mode";
			}
			configd:help "Port mode";
			description
				"Port mode for this port.  In access mode, a primary
				 VLAND ID must be set.";
		}
		container vlan-parameters {
			configd:help "VLAN parameters for switch port";
			leaf-list vlans {
				must "../../mode = 'trunk'" {
					error-message "VLANs are only allowed in "
						+ "trunk mode";
				}
				type vlan-id;
				configd:help "VLANs allowed to ingress to this port";
				description "VLANs allowed to ingress to this port";
			}
			leaf-list untagged-egress-vlans {
				must "../../mode = 'trunk'" {
					error-message "Untagged egress VLANs are only allowed " +
						      "in trunk mode";
				}
				must "../vlans[. = current()]" {
					error-message "Untagged egress VLAN must be one of the " +
						      "allowed VLANs";
				}
				type vlan-id;
				configd:help "VLANs untagged on egress from this port";
				description "VLANs untagged on egress from this port";
			}
			leaf primary-vlan-id {
				must "not(../../mode = 'trunk') or " +
					"../vlans[. = current()]" {
					error-message "Primary VLAN ID must be one of the " +
						      "allowed VLANs in trunk mode";
				}
				type vlan-id;
				configd:help "VLAN to add to untagged frames when received";
				description
					"VLAN to add to untagged frames when received.  VLAN
					 must be one of the allowed VLANs on this port";
			}
			container qos-parameters {
				list vlan {
					key "vlan-id";
					leaf vlan-id {
						type vlan-id;
					}
				}
				configd:help "Qos parameters for the VLAN";
				description "Qos parameters for the VLAN";
			}
		}
	}

	augment /if:interfaces {
		list switch {
			description
				"Switches are like bridge interfaces but are VLAN aware.
				 Each port that is part of a switch may have a set of
				 allowed vlans, a pvid, and a set of vlans to untag on
				 egress from a port.  By default, no VLANs will be part
				 of a port's configuration and no traffic will be passed.

				 The switch name should not be used as a network interface.
				 Instead a VIF interface on the appropriate VLAN should be
				 configured.";
			configd:create "vyatta-switch-master --action=update -- --name=$VAR(@)";
			configd:delete "vyatta-switch-master --action=delete -- --name=$VAR(@)";
			configd:end "vyatta-switch --action=update-vlans -- --name=$VAR(@)";
			configd:end "vyatta-update-vifs $VAR(@)";
			configd:end "vyatta-intf-end $VAR(@)";
			configd:priority 310;
			configd:help "VLAN aware switch";
			key name;
			leaf name {
				type types:interface-ifname {
					pattern 'sw[0-9]+';
					configd:pattern-help "<swN>";
				}
				description "Name of this VLAN aware switch";
				configd:help "Name of this VLAN aware switch";
			}
			container default-port-parameters {
				description "Default parameters for switch ports";
				configd:help "Default parameters for switch ports";
				uses port-parameters {
					refine mode {
						default "access";
					}
				}
			}
			leaf description {
				type string;
				description "User defined description of this interface";
				configd:help "Interface Description";
				configd:update "ip li set dev $VAR(../@) alias '$VAR(@)'";
				configd:delete "vyatta-interfaces.pl --dev=$VAR(../@) --delete-description";
				configd:priority 321;
			}
			leaf disable {
				type empty;
				description "Disable interface";
				configd:help "Disable interface";
				configd:create "ip link set $VAR(../@) down";
				configd:priority 321;
			}
			leaf mac {
				type types:mac-address;
				description "Media Access Control (MAC) address";
				configd:help "Media Access Control (MAC) address";
				must "not(substring(current(), 1, 2) = '01')" {
					error-message "MAC is a multicast address";
				}
				must "not(substring(current(), 1, 14) = '00:00:5e:00:01')" {
					error-message "MAC is a vrrp mac address";
				}
				must "not(current() = '00:00:00:00:00:00')" {
					error-message "zero is not a valid address";
				}
				configd:create "vyatta-interfaces-bridge --action=set_mac --bridge=$VAR(../@) --val=$VAR(@)";
				configd:delete "vyatta-interfaces-bridge --action=del_mac --bridge=$VAR(../@) --val=$VAR(@)";
				configd:priority 321;
			}
			leaf multicast-router {
				type empty;
				description "Enable multicast forwarding";
				configd:help "Enable multicast forwarding";
				configd:create "vyatta-interfaces-bridge --action=set_multicast_router --bridge=$VAR(../@)";
				configd:delete "vyatta-interfaces-bridge --action=del_multicast_router --bridge=$VAR(../@)";
				configd:priority 321;
			}
			leaf disable-link-detect {
				type empty;
				description "Ignore link state changes";
				configd:help "Ignore link state changes";
				configd:create "vyatta-link-detect $VAR(../@) off";
				configd:delete "vyatta-link-detect $VAR(../@) on";
				configd:priority 321;
			}
			leaf-list physical-switch {
				description "Physical switch identifier. Interfaces belonging to the specified hardware switch
                        will automatically be added to this switch.";
				configd:end "vyatta-switchport --action=process-physical-switch -- --phy-switch=$VAR(@) --sw-name=$VAR(../@)";
				configd:help "Physical switch contained in this switch";
				configd:allowed "vyatta-switchport --action=list-physical-switches";
				configd:priority 321;
				type uint32;
				must "count(/if:interfaces/switch/physical-switch[. = current()]) <= 1" {
						error-message "A physical switch can at most be bound to 1 software switch";
				}
			}
			uses vif:vif-group;
			must "true()" {
				configd:must "validate-vif-vlan-settings(.)";
				error-message
					"Either one or more VIFs share the same VLAN ID without
					 different inner vlans, or one or more VIFs without explicit
					 VLAN ID set match the explicit VLAN ID on another VIF.";
			}
		}

		container switch-state {
			config false;
			configd:get-state "vyatta-switch-state";

			list switches {
				description "State of the switches in the system";
				uses br-state:bridge-state-grp;
				key bridge-name;

				list interfaces {
					description "Member ports of this switch";
					uses br-state:bridge-port-state-grp;
					key port-name;

					container forwarding-database-summary {
						description "MAC forwarding database summary";
						uses br-state:bridge-fdb-state-summary-grp;
					}

					list forwarding-database {
						status deprecated;

						description "Forwarding database for this port on the switch";
						key index;

						leaf index {
							description "Index into the forwarding database";
							type uint32;
						}
						leaf vlan-id {
							description "The VLAN on which is MAC address is reachable";
							type vlan-id;
						}
						leaf mac {
							description "The destination MAC address";
							type types:mac-address;
						}
						leaf updated {
							description "Elapsed time since this entry was last updated";
							type uint32;
							units "seconds";
						}
						leaf used {
							description "Elapsed time since this entry was last used";
							type uint32;
							units "seconds";
						}
						leaf state {
							description "The state of this forwarding database entry";
							type br-state:fdb-state;
						}
					}
					list vlans {
						description "VLAN membership of this port on the switch";

						key vlan-id;
						leaf vlan-id {
							description "The VLAN-ID of the member VLAN";
							type vlan-id;
						}
						leaf primary-vlan-id {
							description "If true, this is the Primary VLAN-ID";
							type boolean;
						}
						leaf egress-untagged {
							description "If true, this VLAN is untagged on egress";
							type boolean;
						}
					}
				}
				list vlan-statistics {
					description "Packet statistics for VLANs on this switch";

					key vlan-id;
					leaf vlan-id {
						description "VLAN identifier";
						type vlan-id;
					}
					leaf rx-packets {
						description "Packets received on this VLAN";
						type uint64;
					}
					leaf rx-bytes {
						description "Bytes received on this VLAN";
						type uint64;
					}
					leaf rx-unicast-packets {
						description "Unicast packets received on this VLAN";
						type uint64;
					}
					leaf rx-non-unicast-packets {
						description "Non-unicast packets received on this VLAN";
						type uint64;
					}
					leaf rx-drops {
						description "Packets dropped at reception on this VLAN";
						type uint64;
					}
					leaf rx-errors {
						description "Packet reception errors on this VLAN";
						type uint64;
					}
					leaf tx-packets {
						description "Packets transmitted on this VLAN";
						type uint64;
					}
					leaf tx-bytes {
						description "Bytes transmitted on this VLAN";
						type uint64;
					}
					leaf tx-unicast-packets {
						description "Unicast packets transmitted on this VLAN";
						type uint64;
					}
					leaf tx-non-unicast-packets {
						description "Non-unicast packets transmitted on this VLAN";
						type uint64;
					}
					leaf tx-drops {
						description "Packets dropped during transmission on this VLAN";
						type uint64;
					}
					leaf tx-errors {
						description "Packet transmission errors on this VLAN";
						type uint64;
					}
				}
			}
		}
	}

	rpc switch-fdb {
		description "Retrieve the contents of the MAC forwarding database for the indicated switch interface";

		configd:call-rpc "vyatta-bridge-get-fdb";

		input {
			leaf switch {
				description "Name of the switch interface to be queried";
				mandatory true;
				type string {
					length 3..15;
					pattern "sw[0-9]+";
				}
			}
			leaf port-name {
				description "Name of the switch port to be queried";
				type types:interface-ifname;
			}
			leaf mac-address {
				description "Particular MAC address to be queried";
				type types:mac-address;
			}
		}
		output {
			uses br-state:bridge-fdb-state-grp;
		}
	}

	augment /sys:system/platf:platform {
		configd:end "vyatta-switch --action=set-default-state";
	}

	augment /if:interfaces {
		configd:end "vyatta-switch --action=set-default-state-and-update";
	}

	augment /service:service/pm:portmonitor {
		configd:end "vyatta-switch --action=set-default-state-and-update";
	}
}
