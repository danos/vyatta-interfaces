module vyatta-op-clear-interfaces-switch-v1 {
	namespace "urn:vyatta.com:mgmt:vyatta-op-clear-interfaces-switch:1";
	prefix vyatta-op-clear-interfaces-switch-v1;

	import vyatta-opd-extensions-v1 {
		prefix opd;
	}
	import vyatta-op-clear-v1 {
		prefix clear;
	}
	import vyatta-op-clear-interfaces-v1 {
		prefix if;
	}
	import vyatta-types-v1 {
		prefix types;
	}

	organization "AT&T Inc.";
	contact
		"AT&T
		 Postal: 208 S. Akard Street
		         Dallas, TX 75202
		         USA
		 Web: www.att.com";

	description
		"Copyright (c) 2018, AT&T Intellectual Property.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		Defines the top 'switch' level under 'clear interfaces' for operational CLI";

	revision 2018-07-17 {
		description "Initial version";
	}

	opd:augment /clear:clear/if:interfaces {
		opd:command switch {
			opd:help "Clear switch interface information";

			opd:argument if-name {
				opd:help "Clear interface information for a given switch interface";
				opd:allowed 'vyatta-interfaces.pl --show switch --filter-out "\."';
				type string {
					pattern 'sw[0-9]+';
					opd:pattern-help "<swN>";
				}

				opd:command vlan {
					opd:help "Clear VLAN information for specified switch";

					opd:argument vlan-id {
						opd:help "VLAN number";
						type types:vlan;

						opd:command statistics {
							opd:help "Clear statistics for specifed VLAN on specified switch";
							opd:on-enter "vyatta-switch-op --action=clear-vlan-stats --switch=$4 --vlan=$6";
						}
					}
					opd:command statistics {
						opd:help "Clear statistics for VLANs on the specified switch";
						opd:on-enter 'vyatta-switch-op --action=clear-vlan-stats --switch=$4';
					}
				}
			}
		}
	}
}
