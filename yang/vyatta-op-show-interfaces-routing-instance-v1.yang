module vyatta-op-show-interfaces-routing-instance-v1 {
	namespace "urn:vyatta.com:mgmt:vyatta-op-show-interfaces-routing-instance:1";
	prefix vyatta-op-show-interfaces-routing-instance-v1;

	import vyatta-opd-extensions-v1 {
		prefix opd;
	}
	import vyatta-op-show-v1 {
		prefix show;
	}
	import vyatta-op-show-interfaces-v1 {
		prefix if;
	}

	organization "AT&T Inc.";
	contact
		"AT&T
		 Postal: 208 S. Akard Street
		         Dallas, TX 75202
		         USA
		 Web: www.att.com";

	description
		"Copyright (c) 2018, AT&T Intellectual Property.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Defines the top 'routing-instance' level under 'show interfaces' for operational CLI";

	revision 2019-08-27 {
		description "Fix the prefix assigned to this module.";
	}

	revision 2018-11-19 {
		description "Initial version";
	}

	opd:augment /show:show/if:interfaces {
		opd:command routing-instance {
			opd:help "Show network interface information for routing-instance";

			opd:argument vrf-name {
				opd:help "Show network interface information for routing-instance";
				opd:allowed 'echo all; echo default; getvrflist --name-only';
				opd:on-enter 'vyatta-show-interfaces.pl --action=show-brief --vrf="$4"';
				type string;

				opd:command counters {
					opd:help "Show network interface counters for routing-instance";
					opd:on-enter 'vyatta-show-interfaces.pl --vrf="$4" --action=show-count';
				}

				opd:command detail {
					opd:help "Show detailed network interface information for routing-instance";
					opd:on-enter 'vyatta-show-interfaces.pl --vrf="$4"';
				}
			}
		}
	}

	opd:augment /show:show/if:interfaces/if:if-name {
		opd:command routing-instance {
			opd:help "Show network interface information for routing-instance";

			opd:argument vrf-name {
				opd:help "Show network interface information for routing-instance";
				opd:allowed 'getvrflist --name-only';
				opd:on-enter 'chvrf "$5" vyatta-show-interfaces.pl --vrf="$5" --intf="$3"';
				type string;
			}
		}
	}
}
