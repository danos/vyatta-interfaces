module vyatta-interfaces-vti-v1 {
	namespace "urn:vyatta.com:mgmt:vyatta-interfaces-vti:1";
	prefix vyatta-interfaces-vti-v1;

	import vyatta-interfaces-v1 {
		prefix if;
	}
	import vyatta-types-v1 {
		prefix types;
	}
	import configd-v1 {
		prefix configd;
	}

	organization "AT&T Inc.";
	contact
		"AT&T
		 Postal: 208 S. Akard Street
		         Dallas, TX 75202
		         USA
		 Web: www.att.com";

	description
		"Copyright (c) 2017, AT&T Intellectual Property.
		 All rights reserved.
		 Copyright (c) 2016 by Brocade Communications Systems, Inc.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 VTI interface configuration";

	revision 2017-10-27 {
		description "Use deferred actions to apply configuration to the interface once created.";
	}

	revision 2017-08-25 {
		description "Make use of if:if-parameter-description grouping";
	}

	revision 2017-01-06 {
		description "Added new CLI to configure multicast on vti interface";
	}

	revision 2016-10-27 {
		description "Validation warning removed from address leaf-list";
	}

	revision 2016-05-09 {
		description "Validation warning added to address leaf-list";
	}

	revision 2015-08-14 {
		description "Initial revision of version 1.";
	}

	augment /if:interfaces {
		list vti {
			configd:priority "381";
			configd:help "Virtual Tunnel interface";
			configd:defer-actions "/opt/vyatta/share/tmplscripts/interfaces/vti/configd_defer.sh";
			configd:begin "/opt/vyatta/share/tmplscripts/interfaces/vti/configd_begin.sh";
			configd:validate "interface-address-check $VAR(@) $VAR(./address/@@)";
			configd:delete "/opt/vyatta/share/tmplscripts/interfaces/vti/configd_delete.sh";
			key "tagnode";
			leaf tagnode {
				type string {
					pattern "vti[0-9]+" {
						error-message "vti must be (vti0-vti999..)";
					}
					configd:pattern-help "<vtiN>";
				}
				configd:help "Virtual Tunnel interface";
			}
			uses if:if-parameter-description;
			leaf mtu {
				type uint32 {
					range 68..9000 {
						error-message "Must be between 68-9000";
					}
				}
				configd:priority "382";
				configd:help "Maximum Transmission Unit (MTU)";
				configd:update "/opt/vyatta/share/tmplscripts/interfaces/vti/mtu/configd_update.sh";
				configd:delete "/opt/vyatta/share/tmplscripts/interfaces/vti/mtu/configd_delete.sh";
			}
			leaf disable {
				type empty;
				configd:help "Disable interface";
				configd:create "/opt/vyatta/share/tmplscripts/interfaces/vti/disable/configd_create.sh";
				configd:delete "/opt/vyatta/share/tmplscripts/interfaces/vti/disable/configd_delete.sh";
			}
			leaf-list address {
				type union {
					type types:ipv4-prefix;
					type types:ipv6-prefix;
				}
				ordered-by "user";
				configd:help "IP address";
				configd:create "/opt/vyatta/share/tmplscripts/interfaces/vti/address/configd_create.sh";
			}
			container ip {
				configd:help "IPv4 parameters";
			}
			container ipv6 {
				presence "true";
				configd:help "IPv6 parameters";
			}
			leaf multicast {
				type enumeration {
					enum "enable" {
						configd:help "Enable Multicast (default)";
					}
					enum "disable" {
						configd:help "Disable Multicast";
					}
				}
				configd:help "Multicast operation over vti interface";
				default "enable";
				configd:update "/opt/vyatta/share/tmplscripts/interfaces/vti/multicast/configd_update.sh";
			}
		}
	}
}
