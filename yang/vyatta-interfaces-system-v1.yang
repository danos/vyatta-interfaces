module vyatta-interfaces-system-v1 {
	namespace "urn:vyatta.com:mgmt:vyatta-interfaces-system-v1:1";
	prefix interfaces-system;

	import vyatta-types-v1 {
		prefix types;
	}
	import configd-v1 {
		prefix configd;
	}
	import vyatta-interfaces-v1 {
		prefix if;
	}
	import vyatta-interfaces-system-groups-v1 {
		prefix ifsys;
	}

	organization "AT&T Inc.";
	contact
		"AT&T
		 Postal: 208 S. Akard Street
		         Dallas, TX 75202
		         USA
		 Web: www.att.com";

	description
		"Copyright (c) 2017-2021, AT&T Intellectual Property.
		 All rights reserved.

		 Copyright (c) 2016-2017 by Brocade Communication Systems, Inc.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Local kernel managed (administrative) system
		 interface configuration";

	revision 2021-06-21 {
		description
			"Fix unsafe escape sequence in double-quoted string";
	}

	revision 2017-05-16 {
		description
			"Call script specific to system interface at configd:end
			 to ensure persistent static addresses at reboot";
	}

	revision 2016-09-14 {
		description "Initial revision for version 1";
	}

	augment /if:interfaces {
		list system {
			/*
			 * Need the system interfaces to be handled
			 * (long) before any distributed configuration
			 * (610) and ideally before any other interfaces
			 * (318).
			 */
			configd:priority "310";
			configd:help "Local administrative ethernet interface";
			description "Local administrative ethernet interface";
			configd:allowed 'vyatta-interfaces.pl --show=system --filter="\.[0-9]+"';
			configd:validate "interface-address-check $VAR(@) $VAR(./address/@@)";
			configd:create "vyatta-system-interface --action=create --device=$VAR(@)";
			configd:delete "vyatta-system-interface --action=delete --device=$VAR(@)";
			configd:end "vyatta-system-intf-end $VAR(@)";
			key "ifname";
			leaf ifname {
				type types:interface-ifname;
			}

			uses ifsys:if-parameters-sys;

			list vif {
				configd:priority "311";
				description "Virtual Interface (VIF) ID";
				configd:help "Virtual Interface (VIF) ID";
				configd:validate "interface-address-check $VAR(../@).$VAR(@) $VAR(./address/@@)";
				configd:create "vyatta-system-interface --action=create --device=$VAR(../@) --vif=$VAR(@)";
				configd:delete "vyatta-system-interface --action=delete --device=$VAR(../@) --vif=$VAR(@)";
				configd:end "vyatta-system-intf-end $VAR(../@).$VAR(@)";

				key "tagnode";
				leaf tagnode {
					type uint32 {
						range 1..99999;
					}
					description "Virtual Interface (VIF) ID";
					configd:help "Virtual Interface (VIF) ID";
				}

				uses ifsys:vif-parameters-sys;
				unique "vlan inner-vlan";
			}
		}
	}
}
