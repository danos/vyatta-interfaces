module vyatta-interfaces-tunnel-transport-routing-instance-v1 {
	namespace "urn:vyatta.com:mgmt:vyatta-interfaces-tunnel-transport-routing-instance:1";
	prefix vyatta-interfaces-tunnel-transport-routing-instance-v1;

	import vyatta-interfaces-v1 {
		prefix if;
	}
	import configd-v1 {
		prefix configd;
	}
	import vyatta-interfaces-tunnel-v1 {
		prefix tun;
	}
	import vyatta-routing-v1 {
		prefix rd;
	}

	organization "AT&T";
	contact
		"AT&T
		 Postal: 208 S. Akard Street
		 	 Dallas, TX 75202
		 	 USA
		 Web: www.att.com";

	description
		"Copyright (c) 2017, AT&T Intellectual Property.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Tunnel interface configuration";

	revision 2017-12-05 {
		description "Initial revision of version 1.";
	}

	augment /if:interfaces/tun:tunnel/tun:transport {
		leaf routing-instance {
		        must "(/if:interfaces/tun:tunnel/tun:encapsulation = 'vxlan') or
		              (/if:interfaces/tun:tunnel/tun:encapsulation = 'vxlan-gpe')" {
		             error-message "Transport routing instance can only be specified 
		                            when the encapsulation is vxlan or vxlan-gpe";
		        }
		        type leafref {
		             path "/rd:routing/rd:routing-instance/rd:instance-name";
		        }
		        configd:help "Routing Domain used for the transport network";
		}
	}
}
