module vyatta-interfaces-switch-policy-v1 {
	namespace "urn:vyatta.com:mgmt:vyatta-interfaces-switch-policy:1";
	prefix vyatta-interfaces-switch-policy-v1;

	import vyatta-policy-v1 {
		prefix policy;
	}
	import vyatta-interfaces-v1 {
		prefix if;
	}
	import vyatta-interfaces-dataplane-v1 {
		prefix dp;
	}
	import vyatta-interfaces-dataplane-switch-v1 {
		prefix dp-sw;
	}
	import vyatta-interfaces-switch-v1 {
		prefix sw;
	}
	import vyatta-interfaces-bonding-v1 {
		prefix bonding;
	}
	import vyatta-interfaces-bonding-switch-v1 {
		prefix bd-sw;
	}


	organization "AT&T Inc.";
	contact
		"AT&T
		 Postal: 208 S. Akard Street
		         Dallas, TX 75202
		         USA
		 Web: www.att.com";

	description
		"Copyright (c) 2018-2021 AT&T Intellectual Property
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 The YANG module for enabling policy configuration on switch interfaces";

	revision 2021-09-21 {
		description "Remove unused policy node.";
	}
	revision 2021-07-26 {
		description "Added support for per VLAN QoS on LAG.";
	}
	revision 2021-01-07 {
		description "Added support for LAG QoS.";
	}
	revision 2018-08-27 {
		description "Added Qos policies under the interface
			     switch-group CLI tree.";
	}
	revision 2018-03-08 {
		description "Initial revision of version 1.";
	}

	feature hardware-qos-bond {
		description "Hardware-based QoS on bonding groups";
	}

	augment /if:interfaces/dp:dataplane/dp-sw:switch-group/dp-sw:port-parameters {
		uses policy:policy-binding;
	}

	augment /if:interfaces/bonding:bonding/bd-sw:switch-group/bd-sw:port-parameters {
		if-feature hardware-qos-bond;
		uses policy:policy-binding;
	}

	augment /if:interfaces/bonding:bonding/bd-sw:switch-group/bd-sw:port-parameters/bd-sw:vlan-parameters/bd-sw:qos-parameters/bd-sw:vlan {
		if-feature hardware-qos-bond;
		uses policy:policy-binding;
	}

	augment /if:interfaces/dp:dataplane/dp-sw:switch-group/dp-sw:port-parameters/dp-sw:vlan-parameters/dp-sw:qos-parameters/dp-sw:vlan {
		uses policy:policy-binding;
	}

	augment /if:interfaces/sw:switch/sw:default-port-parameters/sw:vlan-parameters/sw:qos-parameters/sw:vlan {
		uses policy:policy-binding;
	}
}
