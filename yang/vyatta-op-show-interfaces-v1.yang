module vyatta-op-show-interfaces-v1 {
	namespace "urn:vyatta.com:mgmt:vyatta-op-show-interfaces:1";
	prefix vyatta-op-show-interfaces-v1;

	import vyatta-opd-extensions-v1 {
		prefix opd;
	}
	import vyatta-op-show-v1 {
		prefix show;
	}

	organization "Ciena Corporation";
	contact
		"Web URL: https://www.ciena.com/
		 Postal:  7035 Ridge Road
		          Hanover, Maryland 21076
		          U.S.A.
		 Phone:   +1 800-921-1144
		 Fax:     +1 410-694-5750";

	description
		"Copyright (c) 2021, Ciena Corporation, All Rights Reserved.

		 Copyright (c) 2018, AT&T Intellectual Property.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Defines the top 'interfaces' level under 'show' for operational CLI";

	revision 2021-11-15 {
		description "Add per interface filtering to extensive command";
	}

	revision 2018-11-14 {
		description "Convert counters, detail and extensive templates";
	}

	revision 2018-01-29 {
		description "Initial version";
	}

	opd:augment /show:show {
		opd:command interfaces {
			opd:help "Show system interface information";
			opd:on-enter 'vyatta-show-interfaces.pl --action=show-brief';

			opd:argument if-name {
				opd:help "Show specified interface information";
				opd:allowed 'vyatta-interfaces.pl --show all';
				opd:on-enter 'vyatta-show-interfaces.pl --intf="$3" --action=show';
				type string;
			}

			opd:command counters {
				opd:help "Show network interface counters";
				opd:on-enter 'vyatta-show-interfaces.pl --action=show-count';
			}

			opd:command detail {
				opd:help "Show detailed information of all interfaces";
				opd:on-enter 'vyatta-show-interfaces.pl --action=show';
			}

			opd:command extensive {
				opd:help "Show extensive information of all interfaces";
				opd:on-enter 'vyatta-show-interfaces.pl --action=show-extensive';

				opd:argument if-name {
					opd:help "Show extensive information for specified interface";
					opd:allowed 'vyatta-interfaces.pl --show dataplane';
					opd:on-enter 'vyatta-show-interfaces.pl --intf="$4" --action=show-extensive';
					type string;
				}
			}
		}
	}
}
