module vyatta-interfaces-switch-deviations-siad-v1 {
	namespace "urn:vyatta.com:mgmt:vyatta-interfaces-switch-deviations-siad:1";
	prefix vyatta-interfaces-switch-deviations-siad-v1;

	import vyatta-interfaces-v1 {
		prefix if;
	}

	import vyatta-interfaces-switch-v1 {
		prefix switch;
	}

	import configd-v1 {
	        prefix configd;
	}

	organization "AT&T Inc.";
	contact
		"AT&T
		 Postal: 208 S. Akard Street
			 Dallas, TX 75202
		 Web: www.att.com";

	description
		"Copyright (c) 2019, AT&T Intellectual Property.
		 All rights reserved.

		 Redistribution and use in source and binary forms, with or
		 without modification, are permitted provided that the following
		 conditions are met:

		 1. Redistributions of source code must retain the above copyright
			notice, this list of conditions and the following disclaimer.
		 2. Redistributions in binary form must reproduce the above
			copyright notice, this list of conditions and the following
			disclaimer in the documentation and/or other materials provided
			with the distribution.
		 3. Neither the name of the copyright holder nor the names of its
			contributors may be used to endorse or promote products derived
			from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Switch interface configuration deviations";

	revision 2019-12-05 {
		description "Do not allow mac address to be set on switch on siad hardware";
	}

	deviation /if:interfaces/switch:switch/switch:mac {
		description "Media Access Control (MAC) address. Not supported on this platform due to hardware limitations";
		deviate delete {
			configd:help "Media Access Control (MAC) address";
			configd:create "vyatta-interfaces-bridge --action=set_mac --bridge=$VAR(../@) --val=$VAR(@)";
			configd:delete "vyatta-interfaces-bridge --action=del_mac --bridge=$VAR(../@) --val=$VAR(@)";
			configd:priority 321;
		}
		deviate add {
			configd:help "Media Access Control (MAC) address (not supported on this platform)";
			configd:create "echo MAC on switch ignored - not supported on this platform";
			configd:create "logger MAC on switch ignored - not supported on this platform";
		}
	}
}
